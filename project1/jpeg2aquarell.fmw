FME workspace jpeg2aquarell.fmw

Parameters:
- SourceDataset_JPEG = $(FME_MF_DIR)Capture.JPG   # Source JPEG File(s)

Readers:
- JPEG_1: JPEG from $(SourceDataset_JPEG)

JPEG (reader JPEG_1)
    -> JPEG
    -> RasterToPolygonCoercer
Note: https://www.youtube.com/watch?v=5R9eywArFTE&t=1954s
JPEG: Inspector
RasterToPolygonCoercer
    EXTRACT_NODATA = No
    LABEL_ATTRIBUTE = _label
    PRESERVE_ATTRIBUTES = Yes
    POLYGONS -> Counter
Counter
    CNT_ATTR = _count
    DOMAIN = counter
    SCOPE = Global
    START = 0
    -> Tester
Tester
    BOOL_OP = OR
    COMPOSITE_TEST = 1
    TEST_CLAUSE = TEST @Value(_count) = 4371
    TEST_MODE = TEST
    PASSED -> Generalizer
Generalizer
    ALG_TEXT = Douglas (Generalize)
    PRESERVE = No
    PRESERVE_PATHS = No
    TOLERANCE = 10
    -> HullAccumulator
HullAccumulator
    3DMODE_PARAM = 2D
    ACCUM_INPUT_ATTRS = Use Attributes From One Feature
    HULLTYPE_PARAM = Convex ()
    HULL -> GeometryCoercer
GeometryCoercer
    GQUERY:
      for $geom in //geometry
      where $geom/count(parent::geometry) = 0
      return number($geom/@fme_id)
    KIND = fme_line
    COERCED -> CoordinateExtractor
CoordinateExtractor
    LIST_NAME = _indices
    MODE = All Coordinates
    -> PythonCaller
PythonCaller
    PYTHONSOURCE:
      import fme
      import fmeobjects

      import itertools
      def pairwise(iterable):
          "s -> (s0,s1), (s1,s2), (s2, s3), ..."
          a, b = itertools.tee(iterable)
          next(b, None)
          return zip(a, b)

      def processFeature(feature):
          x = feature.getAttribute('_indices{}.x')
          y = feature.getAttribute('_indices{}.y')

          xy = zip(x,y)
          print('123')
          print(xy)
          xy = [i for i in xy]
          print(xy)
          listan = [(a,b) for a, b in zip(xy, xy[1:] + xy[:1])]
          print(listan)



      """
      class FeatureProcessor(object):
          def __init__(self):
              pass
              self.coords = dict()
          def input(self,feature):
              self.coords

              self.pyoutput(feature)

          def close(self):
              pass

      """
    PYTHONSYMBOL = processFeature
    -> PythonCaller_Output
Note: Iterate a list as pair (current, next) in Python
PythonCaller_Output: Inspector
